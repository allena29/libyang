module b {


  namespace "urn:b";
  prefix "b";

  include c {
    revision-date "2026-01-09";
  }
  include d {
    revision-date "2026-01-09";
  }
  revision 2026-01-09 {
    description "example";
  }
}
